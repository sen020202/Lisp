(defun C:RBG ( / ent selset blocklist)
  (setq selset (ssget "X"))
  (if (/= selset nil)
    (setq blocklist (ssget "X" '(0 . "BLOCK")))
    (foreach block blocklist
      (setq blockname (cdr (assoc 'name (entget block))))
      (if (and (wcmatch blockname "*SIGN~V~POT~BUS_*") (not (wcmatch blockname "SIGN~V~POT~BUS")))
        	(command "rename" block "SIGN~V~POT~BUS")
      (if (and (wcmatch blockname "*CR~LEVER~P~LEVE_*") (not (wcmatch blockname "CR~LEVER~P~LEVE")))
        	(command "rename" block "CR~LEVER~P~LEVE")
	(if (and (wcmatch blockname "*CR~LEVER~P~PONCTUEL_*") (not (wcmatch blockname "CR~LEVER~P~PONCTUEL")))
        	(command "rename" block "CR~LEVER~P~PONCTUEL")
	(if (and (wcmatch blockname "*MOB~DECH~CONT~-_*") (not (wcmatch blockname "MOB~DECH~CONT~-")))
        	(command "rename" block "MOB~DECH~CONT~-")
	(if (and (wcmatch blockname "*MOB~DECH~CORB~-_*") (not (wcmatch blockname "MOB~DECH~CORB~-")))
        	(command "rename" block "MOB~DECH~CORB~-")
	(if (and (wcmatch blockname "*MOB~DECH~POUB~-_*") (not (wcmatch blockname "MOB~DECH~POUB~-")))
        	(command "rename" block "MOB~DECH~POUB~-")
	(if (and (wcmatch blockname "*MOB~PROT~BALI~-_*") (not (wcmatch blockname "MOB~PROT~BALI~-")))
       	 	(command "rename" block "MOB~PROT~BALI~-")
	(if (and (wcmatch blockname "*MOB~PROT~BLOC~CAR_*") (not (wcmatch blockname "MOB~PROT~BLOC~CAR")))
       		 (command "rename" block "MOB~PROT~BLOC~CAR")
	(if (and (wcmatch blockname "*DELIM~DP~AMOR~-_*") (not (wcmatch blockname "DELIM~DP~AMOR~-")))
       		 (command "rename" block "DELIM~DP~AMOR~-")
	(if (and (wcmatch blockname "*RESEAU~00~VAN~CAR_*") (not (wcmatch blockname "RESEAU~00~VAN~CAR")))
       		 (command "rename" block "RESEAU~00~VAN~CAR")
	(if (and (wcmatch blockname "*RESEAU~00~VAN~CIR_*") (not (wcmatch blockname "RESEAU~00~VAN~CIR")))
       		 (command "rename" block "RESEAU~00~VAN~CIR")
	(if (and (wcmatch blockname "*RESEAU~00~VAN~PEN_*") (not (wcmatch blockname "RESEAU~00~VAN~PEN")))
       		 (command "rename" block "RESEAU~00~VAN~PEN")
	(if (and (wcmatch blockname "*RESEAU~00~POT~00_*") (not (wcmatch blockname "RESEAU~00~POT~00")))
       		 (command "rename" block "RESEAU~00~POT~00")
	(if (and (wcmatch blockname "*RESEAU~00~REP~-_*") (not (wcmatch blockname "RESEAU~00~REP~-")))
       		 (command "rename" block "RESEAU~00~REP~-")
	(if (and (wcmatch blockname "*RESEAU~AEP~BOU~ARRO_*") (not (wcmatch blockname "RESEAU~AEP~BOU~ARRO")))
       		 (command "rename" block "RESEAU~AEP~BOU~ARRO")
	(if (and (wcmatch blockname "*RESEAU~AEP~BOU~LAVA_*") (not (wcmatch blockname "RESEAU~AEP~BOU~LAVA")))
      		  (command "rename" block "RESEAU~AEP~BOU~LAVA")
	(if (and (wcmatch blockname "*RESEAU~AEP~VAN~CAR_*") (not (wcmatch blockname "RESEAU~AEP~VAN~CAR")))
      		  (command "rename" block "RESEAU~AEP~VAN~CAR")
	(if (and (wcmatch blockname "*RESEAU~AEP~VAN~CIR_*") (not (wcmatch blockname "RESEAU~AEP~VAN~CIR")))
       		 (command "rename" block "RESEAU~AEP~VAN~CIR")
	(if (and (wcmatch blockname "*RESEAU~AEP~VAN~PEN_*") (not (wcmatch blockname "RESEAU~AEP~VAN~PEN")))
       		 (command "rename" block "RESEAU~AEP~VAN~PEN")
	(if (and (wcmatch blockname "*RESEAU~AEP~VAN~REC_*") (not (wcmatch blockname "RESEAU~AEP~VAN~REC")))
       		 (command "rename" block "RESEAU~AEP~VAN~REC")
	(if (and (wcmatch blockname "*RESEAU~AEP~FONT~-_*") (not (wcmatch blockname "RESEAU~AEP~FONT~-")))
       		 (command "rename" block "RESEAU~AEP~FONT~-")
	(if (and (wcmatch blockname "*RESEAU~AEP~REP~-_*") (not (wcmatch blockname "RESEAU~AEP~REP~-")))
       		 (command "rename" block "RESEAU~AEP~REP~-")
	(if (and (wcmatch blockname "*RESEAU~ASSA~VAN~-_*") (not (wcmatch blockname "RESEAU~ASSA~VAN~-")))
      		  (command "rename" block "RESEAU~ASSA~VAN~-")
	(if (and (wcmatch blockname "*RESEAU~CHAU~VAN~CAR_*") (not (wcmatch blockname "RESEAU~CHAU~VAN~CAR")))
      		  (command "rename" block "RESEAU~CHAU~VAN~CAR")
	(if (and (wcmatch blockname "*RESEAU~CHAU~VAN~CIR_*") (not (wcmatch blockname "RESEAU~CHAU~VAN~CIR")))
       		 (command "rename" block "RESEAU~CHAU~VAN~CIR")
	(if (and (wcmatch blockname "*RESEAU~CHAU~VAN~OVA_*") (not (wcmatch blockname "RESEAU~CHAU~VAN~OVA")))
        	(command "rename" block "RESEAU~CHAU~VAN~OVA")
	(if (and (wcmatch blockname "*RESEAU~CHAU~VAN~PEN_*") (not (wcmatch blockname "RESEAU~CHAU~VAN~PEN")))
       		 (command "rename" block "RESEAU~CHAU~VAN~PEN")
	(if (and (wcmatch blockname "*RESEAU~CHAU~REP~-_*") (not (wcmatch blockname "RESEAU~CHAU~REP~-")))
        	(command "rename" block "RESEAU~CHAU~REP~-")
	(if (and (wcmatch blockname "*RESEAU~ECL~LAMP~S_*") (not (wcmatch blockname "RESEAU~ECL~LAMP~S")))
      		 (command "rename" block "RESEAU~ECL~LAMP~S")
	(if (and (wcmatch blockname "*RESEAU~ECL~LAMP~D_*") (not (wcmatch blockname "RESEAU~ECL~LAMP~D")))
        (command "rename" block "RESEAU~ECL~LAMP~D")
	(if (and (wcmatch blockname "*RESEAU~ECL~LAMP~T_*") (not (wcmatch blockname "RESEAU~ECL~LAMP~T")))
        (command "rename" block "RESEAU~ECL~LAMP~T")
	(if (and (wcmatch blockname "*RESEAU~ECL~LAMP~Q_*") (not (wcmatch blockname "RESEAU~ECL~LAMP~Q")))
        (command "rename" block "RESEAU~ECL~LAMP~Q")
	(if (and (wcmatch blockname "*RESEAU~ECL~SUP~-_*") (not (wcmatch blockname "RESEAU~ECL~SUP~-")))
        (command "rename" block "RESEAU~ECL~SUP~-")
	(if (and (wcmatch blockname "*RESEAU~ECL~REP~-_*") (not (wcmatch blockname "RESEAU~ECL~REP~-")))
        (command "rename" block "RESEAU~ECL~REP~-")
	(if (and (wcmatch blockname "*RESEAU~ECL~LUMI~CONS_*") (not (wcmatch blockname "RESEAU~ECL~LUMI~CONS")))
        (command "rename" block "RESEAU~ECL~LUMI~CONS")
	(if (and (wcmatch blockname "*RESEAU~ECL~LUMI~SUS_*") (not (wcmatch blockname "RESEAU~ECL~LUMI~SUS")))
        (command "rename" block "RESEAU~ECL~LUMI~SUS")
	(if (and (wcmatch blockname "*RESEAU~VIDEO~CAM~CONS_*") (not (wcmatch blockname "RESEAU~VIDEO~CAM~CONS")))
        (command "rename" block "RESEAU~VIDEO~CAM~CONS")
	(if (and (wcmatch blockname "*RESEAU~VIDEO~CAM~POT_*") (not (wcmatch blockname "RESEAU~VIDEO~CAM~POT")))
        (command "rename" block "RESEAU~VIDEO~CAM~POT")
	(if (and (wcmatch blockname "*RESEAU~VIDEO~POT_FEU~ACCES_*") (not (wcmatch blockname "RESEAU~VIDEO~POT_FEU~ACCES")))
        (command "rename" block "RESEAU~VIDEO~POT_FEU~ACCES")
	(if (and (wcmatch blockname "*RESEAU~ELEC~SUP~BT_CAR_*") (not (wcmatch blockname "RESEAU~ELEC~SUP~BT_CAR")))
        (command "rename" block "RESEAU~ELEC~SUP~BT_CAR")
	(if (and (wcmatch blockname "*RESEAU~ELEC~SUP~BT_CIR_*") (not (wcmatch blockname "RESEAU~ELEC~SUP~BT_CIR")))
        (command "rename" block "RESEAU~ELEC~SUP~BT_CIR")
	(if (and (wcmatch blockname "*RESEAU~ELEC~SUP~MT_*") (not (wcmatch blockname "RESEAU~ELEC~SUP~MT")))
        (command "rename" block "RESEAU~ELEC~SUP~MT")
	(if (and (wcmatch blockname "*RESEAU~ELEC~SUP~HT_*") (not (wcmatch blockname "RESEAU~ELEC~SUP~HT")))
        (command "rename" block "RESEAU~ELEC~SUP~HT")
	(if (and (wcmatch blockname "*RESEAU~ELEC~SUP~THT_*") (not (wcmatch blockname "RESEAU~ELEC~SUP~THT")))
        (command "rename" block "RESEAU~ELEC~SUP~THT")
	(if (and (wcmatch blockname "*RESEAU~ELEC~PRISE~-_*") (not (wcmatch blockname "RESEAU~ELEC~PRISE~-")))
        (command "rename" block "RESEAU~ELEC~PRISE~-")
	(if (and (wcmatch blockname "*RESEAU~ELEC~REP~-_*") (not (wcmatch blockname "RESEAU~ELEC~REP~-")))
        (command "rename" block "RESEAU~ELEC~REP~-")
	(if (and (wcmatch blockname "*RESEAU~COM~SUP~REN_O_*") (not (wcmatch blockname "RESEAU~COM~SUP~REN_O")))
        (command "rename" block "RESEAU~COM~SUP~REN_O")
	(if (and (wcmatch blockname "*RESEAU~COM~SUP~REN_N_*") (not (wcmatch blockname "RESEAU~COM~SUP~REN_N")))
        (command "rename" block "RESEAU~COM~SUP~REN_N")
	(if (and (wcmatch blockname "*RESEAU~COM~REP~-_*") (not (wcmatch blockname "RESEAU~COM~REP~-")))
        (command "rename" block "RESEAU~COM~REP~-")
	(if (and (wcmatch blockname "*RESEAU~GAZ~VAN~CAR_*") (not (wcmatch blockname "RESEAU~GAZ~VAN~CAR")))
        (command "rename" block "RESEAU~GAZ~VAN~CAR")
	(if (and (wcmatch blockname "*RESEAU~GAZ~VAN~CIR_*") (not (wcmatch blockname "RESEAU~GAZ~VAN~CIR")))
        (command "rename" block "RESEAU~GAZ~VAN~CIR")
	(if (and (wcmatch blockname "*RESEAU~GAZ~VAN~OVA_*") (not (wcmatch blockname "RESEAU~GAZ~VAN~OVA")))
        (command "rename" block "RESEAU~GAZ~VAN~OVA")
	(if (and (wcmatch blockname "*RESEAU~GAZ~VAN~PEN_*") (not (wcmatch blockname "RESEAU~GAZ~VAN~PEN")))
        (command "rename" block "RESEAU~GAZ~VAN~PEN")
	(if (and (wcmatch blockname "*RESEAU~GAZ~REP~-_*") (not (wcmatch blockname "RESEAU~GAZ~REP~-")))
        (command "rename" block "RESEAU~GAZ~REP~-")
	(if (and (wcmatch blockname "*RESEAU~INCE~BORN~-_*") (not (wcmatch blockname "RESEAU~INCE~BORN~-")))
        (command "rename" block "RESEAU~INCE~BORN~-")
	(if (and (wcmatch blockname "*RESEAU~INCE~MAT~-_*") (not (wcmatch blockname "RESEAU~INCE~MAT~-")))
        (command "rename" block "RESEAU~INCE~MAT~-")
	(if (and (wcmatch blockname "*RESEAU~SLT~FLASH~-_*") (not (wcmatch blockname "RESEAU~SLT~FLASH~-")))
        (command "rename" block "RESEAU~SLT~FLASH~-")
	(if (and (wcmatch blockname "*RESEAU~SLT~LUMI~SOL_*") (not (wcmatch blockname "RESEAU~SLT~LUMI~SOL")))
        (command "rename" block "RESEAU~SLT~LUMI~SOL")
	(if (and (wcmatch blockname "*RESEAU~SLT~POT_FEU~PIET_*") (not (wcmatch blockname "RESEAU~SLT~POT_FEU~PIET")))
        (command "rename" block "RESEAU~SLT~POT_FEU~PIET")
	(if (and (wcmatch blockname "*RESEAU~SLT~POT_FEU~UNI_*") (not (wcmatch blockname "RESEAU~SLT~POT_FEU~UNI")))
        (command "rename" block "RESEAU~SLT~POT_FEU~UNI")
	(if (and (wcmatch blockname "*RESEAU~SLT~POT_TRI~MAT_*") (not (wcmatch blockname "RESEAU~SLT~POT_TRI~MAT")))
        (command "rename" block "RESEAU~SLT~POT_TRI~MAT")
	(if (and (wcmatch blockname "*RESEAU~SLT~POT_TRI~POTEN_*") (not (wcmatch blockname "RESEAU~SLT~POT_TRI~POTEN")))
        (command "rename" block "RESEAU~SLT~POT_TRI~POTEN")
	(if (and (wcmatch blockname "*RESEAU~SLT~POT_TRI~00_*") (not (wcmatch blockname "RESEAU~SLT~POT_TRI~00")))
        (command "rename" block "RESEAU~SLT~POT_TRI~00")
	(if (and (wcmatch blockname "*RESEAU~SLT~POT~VARIA_*") (not (wcmatch blockname "RESEAU~SLT~POT~VARIA")))
        (command "rename" block "RESEAU~SLT~POT~VARIA")
	(if (and (wcmatch blockname "*RESEAU~SLT~REP_*") (not (wcmatch blockname "RESEAU~SLT~REP")))
        (command "rename" block "RESEAU~SLT~REP")
	(if (and (wcmatch blockname "*RESEAU~TRANS~CATE~S_*") (not (wcmatch blockname "RESEAU~TRANS~CATE~S")))
        (command "rename" block "RESEAU~TRANS~CATE~S")
	(if (and (wcmatch blockname "*RESEAU~TRANS~CATE~D_*") (not (wcmatch blockname "RESEAU~TRANS~CATE~D")))
        (command "rename" block "RESEAU~TRANS~CATE~D")
	(if (and (wcmatch blockname "*RESEAU~TRANS~POT_FEU~TRAM_*") (not (wcmatch blockname "RESEAU~TRANS~POT_FEU~TRAM")))
        (command "rename" block "RESEAU~TRANS~POT_FEU~TRAM")
	(if (and (wcmatch blockname "*RESEAU~TRANS~POT~BUS_*") (not (wcmatch blockname "RESEAU~TRANS~POT~BUS")))
        (command "rename" block "RESEAU~TRANS~POT~BUS")
	(if (and (wcmatch blockname "*RESEAU~TRANS~CAM~POT_*") (not (wcmatch blockname "RESEAU~TRANS~CAM~POT")))
        (command "rename" block "RESEAU~TRANS~CAM~POT")
	(if (and (wcmatch blockname "*RESEAU~TRANS~LIB~-_*") (not (wcmatch blockname "RESEAU~TRANS~LIB~-")))
        (command "rename" block "RESEAU~TRANS~LIB~-")
	(if (and (wcmatch blockname "*RESEAU~TRANS~REP~-_*") (not (wcmatch blockname "RESEAU~TRANS~REP~-")))
        (command "rename" block "RESEAU~TRANS~REP~-")
	(if (and (wcmatch blockname "*MOB~PROT~BALI~-_*") (not (wcmatch blockname "MOB~PROT~BALI~-")))
        (command "rename" block "MOB~PROT~BALI~-")
	(if (and (wcmatch blockname "*MOB~PROT~POT~BAR_N_*") (not (wcmatch blockname "MOB~PROT~POT~BAR_N")))
        (command "rename" block "MOB~PROT~POT~BAR_N")
	(if (and (wcmatch blockname "*MOB~PUB~SUP~MAT_*") (not (wcmatch blockname "MOB~PUB~SUP~MAT")))
        (command "rename" block "MOB~PUB~SUP~MAT")
	(if (and (wcmatch blockname "*MOB~URB~BORN~OGE_*") (not (wcmatch blockname "MOB~URB~BORN~OGE")))
        (command "rename" block "MOB~URB~BORN~OGE")
	(if (and (wcmatch blockname "*MOB~URB~DRAP~-_*") (not (wcmatch blockname "MOB~URB~DRAP~-")))
        (command "rename" block "MOB~URB~DRAP~-")
	(if (and (wcmatch blockname "*SIGN~V~BORN~KILO_*") (not (wcmatch blockname "SIGN~V~BORN~KILO")))
        (command "rename" block "SIGN~V~BORN~KILO")
	(if (and (wcmatch blockname "*SIGN~V~POT_FER~MAT_*") (not (wcmatch blockname "SIGN~V~POT_FER~MAT")))
        (command "rename" block "SIGN~V~POT_FER~MAT")
	(if (and (wcmatch blockname "*SIGN~V~POT_FER~00_*") (not (wcmatch blockname "SIGN~V~POT_FER~00")))
        (command "rename" block "SIGN~V~POT_FER~00")
	(if (and (wcmatch blockname "*SIGN~V~POT_JAL~ITI_*") (not (wcmatch blockname "SIGN~V~POT_JAL~ITI")))
        (command "rename" block "SIGN~V~POT_JAL~ITI")
	(if (and (wcmatch blockname "*SIGN~V~POT_JAL~LOC_*") (not (wcmatch blockname "SIGN~V~POT_JAL~LOC")))
        (command "rename" block "SIGN~V~POT_JAL~LOC")
	(if (and (wcmatch blockname "*SIGN~V~POT_JAL~PUB_*") (not (wcmatch blockname "SIGN~V~POT_JAL~PUB")))
        (command "rename" block "SIGN~V~POT_JAL~PUB")
	(if (and (wcmatch blockname "*SIGN~V~POT_ROU~MAT_*") (not (wcmatch blockname "SIGN~V~POT_ROU~MAT")))
        (command "rename" block "SIGN~V~POT_ROU~MAT")
	(if (and (wcmatch blockname "*SIGN~V~POT_ROU~00_*") (not (wcmatch blockname "SIGN~V~POT_ROU~00")))
        (command "rename" block "SIGN~V~POT_ROU~00")
	(if (and (wcmatch blockname "*SIGN~V~POT~RUE_*") (not (wcmatch blockname "SIGN~V~POT~RUE")))
        (command "rename" block "SIGN~V~POT~RUE")
	(if (and (wcmatch blockname "*SIGN~V~POT~BUS_*") (not (wcmatch blockname "SIGN~V~POT~BUS")))
        (command "rename" block "SIGN~V~POT~BUS")
	(if (and (wcmatch blockname "*SIGN~V~POT~VILLE_*") (not (wcmatch blockname "SIGN~V~POT~VILLE")))
        (command "rename" block "SIGN~V~POT~VILLE")
	(if (and (wcmatch blockname "*DELIM~CLOT~PIL~CAR_*") (not (wcmatch blockname "DELIM~CLOT~PIL~CAR")))
        (command "rename" block "DELIM~CLOT~PIL~CAR")
	(if (and (wcmatch blockname "*DELIM~CLOT~PIL~CIR_*") (not (wcmatch blockname "DELIM~CLOT~PIL~CIR")))
        (command "rename" block "DELIM~CLOT~PIL~CIR")
	(if (and (wcmatch blockname "*DELIM~CLOT~PIL~OVA_*") (not (wcmatch blockname "DELIM~CLOT~PIL~OVA")))
        (command "rename" block "DELIM~CLOT~PIL~OVA")
	(if (and (wcmatch blockname "*DELIM~CLOT~PIL~REC_*") (not (wcmatch blockname "DELIM~CLOT~PIL~REC")))
        (command "rename" block "DELIM~CLOT~PIL~REC")
	(if (and (wcmatch blockname "*INFRA~ROU~RAL~FIXE_*") (not (wcmatch blockname "INFRA~ROU~RAL~FIXE")))
        (command "rename" block "INFRA~ROU~RAL~FIXE")
	(if (and (wcmatch blockname "*NATURE~VERT~ARB~CONI_*") (not (wcmatch blockname "NATURE~VERT~ARB~CONI")))
        (command "rename" block "NATURE~VERT~ARB~CONI")
	(if (and (wcmatch blockname "*NATURE~VERT~FAUNE~-_*") (not (wcmatch blockname "NATURE~VERT~FAUNE~-")))
        (command "rename" block "NATURE~VERT~FAUNE~-")
	(if (and (wcmatch blockname "*NATURE~VERT~BAC~CAR_*") (not (wcmatch blockname "NATURE~VERT~BAC~CAR")))
        (command "rename" block "NATURE~VERT~BAC~CAR")
	(if (and (wcmatch blockname "*NATURE~VERT~BAC~CIR_*") (not (wcmatch blockname "NATURE~VERT~BAC~CIR")))
        (command "rename" block "NATURE~VERT~BAC~CIR")
	(if (and (wcmatch blockname "*NATURE~VERT~BAC~REC_*") (not (wcmatch blockname "NATURE~VERT~BAC~REC")))
        (command "rename" block "NATURE~VERT~BAC~REC")
	(if (and (wcmatch blockname "*RESEAU~00~ARM~ENCA_*") (not (wcmatch blockname "RESEAU~00~ARM~ENCA")))
        (command "rename" block "RESEAU~00~ARM~ENCA")
	(if (and (wcmatch blockname "*RESEAU~00~ARM~00_*") (not (wcmatch blockname "RESEAU~00~ARM~00")))
        (command "rename" block "MOB~PROT~BLOC~CAR")
	(if (and (wcmatch blockname "*RESEAU~00~COF~ENCA_*") (not (wcmatch blockname "RESEAU~00~COF~ENCA")))
        (command "rename" block "RESEAU~00~COF~ENCA")
	(if (and (wcmatch blockname "*RESEAU~00~COF~00_*") (not (wcmatch blockname "RESEAU~00~COF~00")))
        (command "rename" block "RESEAU~00~COF~00")
	(if (and (wcmatch blockname "*RESEAU~00~VAN~OVA_*") (not (wcmatch blockname "RESEAU~00~VAN~OVA")))
        (command "rename" block "RESEAU~00~VAN~OVA")
	(if (and (wcmatch blockname "*RESEAU~00~PLA~CAR_*") (not (wcmatch blockname "RESEAU~00~PLA~CAR")))
        (command "rename" block "RESEAU~00~PLA~CAR")
	(if (and (wcmatch blockname "*RESEAU~00~PLA~REC_*") (not (wcmatch blockname "RESEAU~00~PLA~REC")))
        (command "rename" block "RESEAU~00~PLA~REC")
	(if (and (wcmatch blockname "*RESEAU~CHAU~REG~CAR_*") (not (wcmatch blockname "RESEAU~CHAU~REG~CAR")))
        (command "rename" block "RESEAU~CHAU~REG~CAR")
	(if (and (wcmatch blockname "*RESEAU~00~REG~CAR_*") (not (wcmatch blockname "RESEAU~00~REG~CAR")))
        (command "rename" block "RESEAU~00~REG~CAR")
	(if (and (wcmatch blockname "*RESEAU~00~REG~CIR_*") (not (wcmatch blockname "RESEAU~00~REG~CIR")))
        (command "rename" block "RESEAU~00~REG~CIR")
	(if (and (wcmatch blockname "*RESEAU~00~REG~OVA_*") (not (wcmatch blockname "RESEAU~00~REG~OVA")))
        (command "rename" block "RESEAU~00~REG~OVA")
	(if (and (wcmatch blockname "*RESEAU~00~REG~REC_*") (not (wcmatch blockname "RESEAU~00~REG~REC")))
        (command "rename" block "RESEAU~00~REG~REC")
	(if (and (wcmatch blockname "*RESEAU~AEP~VAN~OVA_*") (not (wcmatch blockname "RESEAU~AEP~VAN~OVA")))
        (command "rename" block "RESEAU~AEP~VAN~OVA")
	(if (and (wcmatch blockname "*RESEAU~AEP~PUITS~-_*") (not (wcmatch blockname "RESEAU~AEP~PUITS~-")))
        (command "rename" block "RESEAU~AEP~PUITS~-")
	(if (and (wcmatch blockname "*RESEAU~ASSA~GRIL~CAR_*") (not (wcmatch blockname "RESEAU~ASSA~GRIL~CAR")))
        (command "rename" block "RESEAU~ASSA~GRIL~CAR")
	(if (and (wcmatch blockname "*RESEAU~ASSA~GRIL~CIR_*") (not (wcmatch blockname "RESEAU~ASSA~GRIL~CIR")))
        (command "rename" block "RESEAU~ASSA~GRIL~CIR")
	(if (and (wcmatch blockname "*RESEAU~ASSA~GRIL~OVA_*") (not (wcmatch blockname "RESEAU~ASSA~GRIL~OVA")))
        (command "rename" block "RESEAU~ASSA~GRIL~OVA")
	(if (and (wcmatch blockname "*RESEAU~ASSA~GRIL~REC_*") (not (wcmatch blockname "RESEAU~ASSA~GRIL~REC")))
        (command "rename" block "RESEAU~ASSA~GRIL~REC")
	(if (and (wcmatch blockname "*RESEAU~ASSA~REG~CAR_*") (not (wcmatch blockname "RESEAU~ASSA~REG~CAR")))
        (command "rename" block "RESEAU~ASSA~REG~CAR")
	(if (and (wcmatch blockname "*RESEAU~ASSA~REG~CIR_*") (not (wcmatch blockname "RESEAU~ASSA~REG~CIR")))
        (command "rename" block "RESEAU~ASSA~REG~CIR")
	(if (and (wcmatch blockname "*RESEAU~CHAU~ARM~ENCA_*") (not (wcmatch blockname "RESEAU~CHAU~ARM~ENCA")))
        (command "rename" block "RESEAU~CHAU~ARM~ENCA")
	(if (and (wcmatch blockname "*RESEAU~CHAU~ARM~00_*") (not (wcmatch blockname "RESEAU~CHAU~ARM~00")))
        (command "rename" block "RESEAU~CHAU~ARM~00")
	(if (and (wcmatch blockname "*RESEAU~CHAU~COF~00_*") (not (wcmatch blockname "RESEAU~CHAU~COF~00")))
        (command "rename" block "RESEAU~CHAU~COF~00")
	(if (and (wcmatch blockname "*RESEAU~CHAU~PLA~CAR_*") (not (wcmatch blockname "RESEAU~CHAU~PLA~CAR")))
        (command "rename" block "RESEAU~CHAU~PLA~CAR")
	(if (and (wcmatch blockname "*RESEAU~CHAU~PLA~REC_*") (not (wcmatch blockname "RESEAU~CHAU~PLA~REC")))
        (command "rename" block "RESEAU~CHAU~PLA~REC")
	(if (and (wcmatch blockname "*RESEAU~CHAU~REG~CIR_*") (not (wcmatch blockname "RESEAU~CHAU~REG~CIR")))
        (command "rename" block "RESEAU~CHAU~REG~CIR")
	(if (and (wcmatch blockname "*RESEAU~CHAU~REG~OVA_*") (not (wcmatch blockname "RESEAU~CHAU~REG~OVA")))
        (command "rename" block "RESEAU~CHAU~REG~OVA")
	(if (and (wcmatch blockname "*RESEAU~CHAU~REG~REC_*") (not (wcmatch blockname "RESEAU~CHAU~REG~REC")))
        (command "rename" block "RESEAU~CHAU~REG~REC")
	(if (and (wcmatch blockname "*RESEAU~ECL~ARM~ENCA_*") (not (wcmatch blockname "RESEAU~ECL~ARM~ENCA")))
        (command "rename" block "RESEAU~ECL~ARM~ENCA")
	(if (and (wcmatch blockname "*RESEAU~ECL~ARM~00_*") (not (wcmatch blockname "RESEAU~ECL~ARM~00")))
        (command "rename" block "RESEAU~ECL~ARM~00")
	(if (and (wcmatch blockname "*RESEAU~ECL~COF~ENCA_*") (not (wcmatch blockname "RESEAU~ECL~COF~ENCA")))
        (command "rename" block "RESEAU~ECL~COF~ENCA")
	(if (and (wcmatch blockname "*RESEAU~ECL~COF~00_*") (not (wcmatch blockname "RESEAU~ECL~COF~00")))
        (command "rename" block "RESEAU~ECL~COF~00")
	(if (and (wcmatch blockname "*RESEAU~ECL~PLA~CAR_*") (not (wcmatch blockname "RESEAU~ECL~PLA~CAR")))
        (command "rename" block "RESEAU~ECL~PLA~CAR")
	(if (and (wcmatch blockname "*RESEAU~ECL~PLA~REC_*") (not (wcmatch blockname "RESEAU~ECL~PLA~REC")))
        (command "rename" block "RESEAU~ECL~PLA~REC")
	(if (and (wcmatch blockname "*RESEAU~ECL~LUMI~CAR_*") (not (wcmatch blockname "RESEAU~ECL~LUMI~CAR")))
        (command "rename" block "RESEAU~ECL~LUMI~CAR")
	(if (and (wcmatch blockname "*RESEAU~ECL~LUMI~CIR_*") (not (wcmatch blockname "RESEAU~ECL~LUMI~CIR")))
        (command "rename" block "RESEAU~ECL~LUMI~CIR")
	(if (and (wcmatch blockname "*RESEAU~ECL~LUMI~OVA_*") (not (wcmatch blockname "RESEAU~ECL~LUMI~OVA")))
        (command "rename" block "RESEAU~ECL~LUMI~OVA")
	(if (and (wcmatch blockname "*RESEAU~ECL~LUMI~REC_*") (not (wcmatch blockname "RESEAU~ECL~LUMI~REC")))
        (command "rename" block "RESEAU~ECL~LUMI~REC")
	(if (and (wcmatch blockname "*RESEAU~VIDEO~BORN~ACCES_*") (not (wcmatch blockname "RESEAU~VIDEO~BORN~ACCES")))
        (command "rename" block "RESEAU~VIDEO~BORN~ACCES")
	(if (and (wcmatch blockname "*RESEAU~VIDEO~BORN~RETRA_*") (not (wcmatch blockname "RESEAU~VIDEO~BORN~RETRA")))
        (command "rename" block "RESEAU~VIDEO~BORN~RETRA")
	(if (and (wcmatch blockname "*RESEAU~ELEC~ARM~ENCA_*") (not (wcmatch blockname "RESEAU~ELEC~ARM~ENCA")))
        (command "rename" block "RESEAU~ELEC~ARM~ENCA")
	(if (and (wcmatch blockname "*RESEAU~ELEC~ARM~00_*") (not (wcmatch blockname "RESEAU~ELEC~ARM~00")))
        (command "rename" block "RESEAU~ELEC~ARM~00")
	(if (and (wcmatch blockname "*RESEAU~ELEC~ARM~00_*") (not (wcmatch blockname "RESEAU~ELEC~ARM~00")))
        (command "rename" block "RESEAU~ELEC~ARM~00")
	(if (and (wcmatch blockname "*RESEAU~ELEC~COF~ENCA_*") (not (wcmatch blockname "RESEAU~ELEC~COF~ENCA")))
        (command "rename" block "RESEAU~ELEC~COF~ENCA")
	(if (and (wcmatch blockname "*RESEAU~ELEC~COF~00_*") (not (wcmatch blockname "RESEAU~ELEC~COF~00")))
        (command "rename" block "RESEAU~ELEC~COF~00")
	(if (and (wcmatch blockname "*RESEAU~ELEC~PLA~CAR_*") (not (wcmatch blockname "RESEAU~ELEC~PLA~CAR")))
        (command "rename" block "RESEAU~ELEC~PLA~CAR")
	(if (and (wcmatch blockname "*RESEAU~ELEC~PLA~REC_*") (not (wcmatch blockname "RESEAU~ELEC~PLA~REC")))
        (command "rename" block "RESEAU~ELEC~PLA~REC")
	(if (and (wcmatch blockname "*RESEAU~ELEC~SUP~PYL_*") (not (wcmatch blockname "RESEAU~ELEC~SUP~PYL")))
        (command "rename" block "RESEAU~ELEC~SUP~PYL")
	(if (and (wcmatch blockname "*RESEAU~COM~COF~ENCA_*") (not (wcmatch blockname "RESEAU~COM~COF~ENCA")))
        (command "rename" block "RESEAU~COM~COF~ENCA")
	(if (and (wcmatch blockname "*RESEAU~COM~COF~MAC_*") (not (wcmatch blockname "RESEAU~COM~COF~MAC")))
        (command "rename" block "RESEAU~COM~COF~MAC")
	(if (and (wcmatch blockname "*RESEAU~COM~COF~00_*") (not (wcmatch blockname "RESEAU~COM~COF~00")))
        (command "rename" block "RESEAU~COM~COF~00")
	(if (and (wcmatch blockname "*RESEAU~COM~PLA~CAR_*") (not (wcmatch blockname "RESEAU~COM~PLA~CAR")))
        (command "rename" block "RESEAU~COM~PLA~CAR")
	(if (and (wcmatch blockname "*RESEAU~COM~PLA~REC_*") (not (wcmatch blockname "RESEAU~COM~PLA~REC")))
        (command "rename" block "RESEAU~COM~PLA~REC")
	(if (and (wcmatch blockname "*RESEAU~INOLIA~PLA~CAR_*") (not (wcmatch blockname "RESEAU~INOLIA~PLA~CAR")))
        (command "rename" block "RESEAU~INOLIA~PLA~CAR")
	(if (and (wcmatch blockname "*RESEAU~INOLIA~PLA~REC_*") (not (wcmatch blockname "RESEAU~INOLIA~PLA~REC")))
        (command "rename" block "RESEAU~INOLIA~PLA~REC")
	(if (and (wcmatch blockname "*RESEAU~INOLIA~REP~-_*") (not (wcmatch blockname "RESEAU~INOLIA~REP~-")))
        (command "rename" block "RESEAU~INOLIA~REP~-")
	(if (and (wcmatch blockname "*RESEAU~GAZ~ARM~ENCA_*") (not (wcmatch blockname "RESEAU~GAZ~ARM~ENCA")))
        (command "rename" block "RESEAU~GAZ~ARM~ENCA")
	(if (and (wcmatch blockname "*RESEAU~GAZ~ARM~00_*") (not (wcmatch blockname "RESEAU~GAZ~ARM~00")))
        (command "rename" block "RESEAU~GAZ~ARM~00")
	(if (and (wcmatch blockname "*RESEAU~GAZ~COF~ENCA_*") (not (wcmatch blockname "RESEAU~GAZ~COF~ENCA")))
        (command "rename" block "RESEAU~GAZ~COF~ENCA")
	(if (and (wcmatch blockname "*RESEAU~GAZ~COF~00_*") (not (wcmatch blockname "RESEAU~GAZ~COF~00")))
        (command "rename" block "RESEAU~GAZ~COF~00")
	(if (and (wcmatch blockname "*RESEAU~GAZ~PLA~CAR_*") (not (wcmatch blockname "RESEAU~GAZ~PLA~CAR")))
        (command "rename" block "RESEAU~GAZ~PLA~CAR")
	(if (and (wcmatch blockname "*RESEAU~GAZ~PLA~REC_*") (not (wcmatch blockname "RESEAU~GAZ~PLA~REC")))
        (command "rename" block "RESEAU~GAZ~PLA~REC")
	(if (and (wcmatch blockname "*RESEAU~GAZ~REG~CAR_*") (not (wcmatch blockname "RESEAU~GAZ~REG~CAR")))
        (command "rename" block "RESEAU~GAZ~REG~CAR")
	(if (and (wcmatch blockname "*RESEAU~GAZ~REG~CIR_*") (not (wcmatch blockname "RESEAU~GAZ~REG~CIR")))
        (command "rename" block "RESEAU~GAZ~REG~CIR")
	(if (and (wcmatch blockname "*RESEAU~GAZ~REG~OVA_*") (not (wcmatch blockname "RESEAU~GAZ~REG~OVA")))
        (command "rename" block "RESEAU~GAZ~REG~OVA")
	(if (and (wcmatch blockname "*RESEAU~GAZ~REG~REC_*") (not (wcmatch blockname "RESEAU~GAZ~REG~REC")))
        (command "rename" block "RESEAU~GAZ~REG~REC")
	(if (and (wcmatch blockname "*RESEAU~INCE~BOU~-_*") (not (wcmatch blockname "RESEAU~INCE~BOU~-")))
        (command "rename" block "RESEAU~INCE~BOU~-")
	(if (and (wcmatch blockname "*RESEAU~SLT~PLA~CAR_*") (not (wcmatch blockname "RESEAU~SLT~PLA~CAR")))
        (command "rename" block "RESEAU~SLT~PLA~CAR")
	(if (and (wcmatch blockname "*RESEAU~SLT~PLA~REC_*") (not (wcmatch blockname "RESEAU~SLT~PLA~REC")))
        (command "rename" block "RESEAU~SLT~PLA~REC")
	(if (and (wcmatch blockname "*RESEAU~SLT~REF~-_*") (not (wcmatch blockname "RESEAU~SLT~REF~-")))
        (command "rename" block "RESEAU~SLT~REF~-")
	(if (and (wcmatch blockname "*RESEAU~TRANS~AUBETTE~BUS_*") (not (wcmatch blockname "RESEAU~TRANS~AUBETTE~BUS")))
        (command "rename" block "RESEAU~TRANS~AUBETTE~BUS")
	(if (and (wcmatch blockname "*RESEAU~TRANS~AUBETTE~TRAM_*") (not (wcmatch blockname "RESEAU~TRANS~AUBETTE~TRAM")))
        (command "rename" block "RESEAU~TRANS~AUBETTE~TRAM")
	(if (and (wcmatch blockname "*RESEAU~TRANS~BORN~TITRE_*") (not (wcmatch blockname "RESEAU~TRANS~BORN~TITRE")))
        (command "rename" block "RESEAU~TRANS~BORN~TITRE")
	(if (and (wcmatch blockname "*RESEAU~TRANS~TITRE~-_*") (not (wcmatch blockname "RESEAU~TRANS~TITRE~-")))
        (command "rename" block "RESEAU~TRANS~TITRE~-")
	(if (and (wcmatch blockname "*MOB~DECH~CONT~-_*") (not (wcmatch blockname "MOB~DECH~CONT~-")))
        (command "rename" block "MOB~DECH~CONT~-")
	(if (and (wcmatch blockname "*MOB~DECH~CORB~-_*") (not (wcmatch blockname "MOB~DECH~CORB~-")))
        (command "rename" block "MOB~DECH~CORB~-")
	(if (and (wcmatch blockname "*MOB~DECH~POUB~-_*") (not (wcmatch blockname "MOB~DECH~POUB~-")))
        (command "rename" block "MOB~DECH~POUB~-")
	(if (and (wcmatch blockname "*MOB~PROT~BORN~CAR_*") (not (wcmatch blockname "MOB~PROT~BORN~CAR")))
        (command "rename" block "MOB~PROT~BORN~CAR")
	(if (and (wcmatch blockname "*MOB~PROT~BLOC~CAR_*") (not (wcmatch blockname "MOB~PROT~BLOC~CAR")))
        (command "rename" block "MOB~PROT~BLOC~CAR")
	(if (and (wcmatch blockname "*MOB~PROT~BLOC~REC_*") (not (wcmatch blockname "MOB~PROT~BLOC~REC")))
        (command "rename" block "MOB~PROT~BLOC~REC")
	(if (and (wcmatch blockname "*MOB~SANI~TOILE~-_*") (not (wcmatch blockname "MOB~SANI~TOILE~-")))
        (command "rename" block "MOB~SANI~TOILE~-")
	(if (and (wcmatch blockname "*MOB~PUB~SUP~CIR_*") (not (wcmatch blockname "MOB~PUB~SUP~CIR")))
        (command "rename" block "MOB~PUB~SUP~CIR")
	(if (and (wcmatch blockname "*MOB~PUB~SUP~REC_*") (not (wcmatch blockname "MOB~PUB~SUP~REC")))
        (command "rename" block "MOB~PUB~SUP~REC")
	(if (and (wcmatch blockname "*MOB~PUB~SUP~TRI_*") (not (wcmatch blockname "MOB~PUB~SUP~TRI")))
        (command "rename" block "MOB~PUB~SUP~TRI")
	(if (and (wcmatch blockname "*MOB~URB~BANC~-_*") (not (wcmatch blockname "MOB~URB~BANC~-")))
        (command "rename" block "MOB~URB~BANC~-")
	(if (and (wcmatch blockname "*MOB~URB~BAL~-_*") (not (wcmatch blockname "MOB~URB~BAL~-")))
        (command "rename" block "MOB~URB~BAL~-")
	(if (and (wcmatch blockname "*MOB~URB~HORO~-_*") (not (wcmatch blockname "MOB~URB~HORO~-")))
        (command "rename" block "MOB~URB~HORO~-")
	(if (and (wcmatch blockname "*MOB~URB~SUP~-_*") (not (wcmatch blockname "MOB~URB~SUP~-")))
        (command "rename" block "MOB~URB~SUP~-")

      )
    )
  )
)
